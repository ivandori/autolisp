;;;=============================================================================
;;; 4. FUNZIONI DIMOSTRATIVE
;;;=============================================================================
;;; CONVERTI-RECORD-STRINGA
;;; Converte un record in stringa leggibile (per output)
(defun converti-record-stringa (record / str pair)
  (setq str "{ ")
  (foreach pair record
    (setq str (strcat str 
                     (if (numberp (car pair))
                       (itoa (car pair))
                       (if (is-string (car pair))
                         (car pair)
                         (princ-to-string (car pair))))
                     ": "))
    (setq str (strcat str
                     (if (numberp (cdr pair))
                       (if (= (fix (cdr pair)) (cdr pair))
                         (itoa (cdr pair))
                         (rtos (cdr pair) 2 2))
                       (if (is-string (cdr pair))
                         (cdr pair)
                         (princ-to-string (cdr pair))))
                     ", ")))
  (setq str (strcat (substr str 1 (- (strlen str) 2)) " }"))
  str)
;;; STAMPA-RECORD
;;; Stampa un record in modo leggibile
(defun stampa-record (record)
  (princ "\n")
  (princ (converti-record-stringa record))
  (princ))
;;; STAMPA-LISTA-RECORD
;;; Stampa una lista di record
(defun stampa-lista-record (record-list / rec idx)
  (setq idx 1)
  (princ "\n")
  (foreach rec record-list
    (princ (strcat "\n[" (itoa idx) "] "))
    (princ (converti-record-stringa rec))
    (setq idx (1+ idx)))
  (princ))
;;; DEMO-GESTIONE-BASE
;;; Dimostra operazioni base su record singolo
(defun c:demo-record-base ()
  (princ "\n=== DEMO GESTIONE BASE RECORD ===")
  (setq persona '((nome . "Mario") (cognome . "Rossi") (eta . 30) (citta . "Milano")))
  (princ "\n\nRecord originale:")
  (stampa-record persona)
  (setq persona (update-field persona 'eta 31))
  (princ "\n\nDopo aggiornamento eta a 31:")
  (stampa-record persona)
  (setq persona (add-field persona 'professione "Ingegnere"))
  (princ "\n\nDopo aggiunta campo professione:")
  (stampa-record persona)
  (setq nome-valore (get-field-value persona 'nome))
  (princ (strcat "\n\nValore campo 'nome': " nome-valore))
  (princ "\n\n=== Demo completata ===")
  (princ))
;;; DEMO-DATABASE
;;; Dimostra operazioni su database (lista di record)
(defun c:demo-record-db ()
  (princ "\n=== DEMO DATABASE RECORD ===")
  (setq persone '(((nome . "Mario") (eta . 30) (citta . "Milano"))
                  ((nome . "Luca") (eta . 25) (citta . "Roma"))
                  ((nome . "Anna") (eta . 28) (citta . "Milano"))
                  ((nome . "Sara") (eta . 35) (citta . "Torino"))
                  ((nome . "Paolo") (eta . 32) (citta . "Milano"))))
  (princ "\n\nDatabase completo:")
  (stampa-lista-record persone)
  (setq trovati (query-records 'citta "Milano" persone))
  (princ "\n\n\nQuery: persone che vivono a Milano:")
  (if (= trovati 'ERRORE)
    (princ "\nNessun record trovato!")
    (stampa-lista-record trovati))
  (setq citta-uniche (extract-field-values persone 'citta))
  (princ "\n\n\nCitta' presenti nel database:")
  (foreach c citta-uniche
    (princ (strcat "\n  - " c)))
  (setq conteggio (count-records 'citta "Milano" persone))
  (princ (strcat "\n\nNumero persone a Milano: " (itoa conteggio)))
  (princ "\n\n=== Demo completata ===")
  (princ))
;;; DEMO-OPERAZIONI-AVANZATE
;;; Dimostra operazioni avanzate
(defun c:demo-record-avanzate ()
  (princ "\n=== DEMO OPERAZIONI AVANZATE ===")
  (setq rec1 '((nome . "Mario") (eta . 30)))
  (setq rec2 '((eta . 31) (citta . "Milano")))
  (princ "\n\nRecord 1:")
  (stampa-record rec1)
  (princ "\n\nRecord 2:")
  (stampa-record rec2)
  (setq rec-unito (merge-records rec1 rec2))
  (princ "\n\nRecord unito (rec2 sovrascrive rec1):")
  (stampa-record rec-unito)
  (setq campi (get-field-names rec-unito))
  (princ "\n\nCampi presenti:")
  (foreach campo campi
    (princ (strcat "\n  - " (princ-to-string campo))))
  (setq rec-senza-eta (remove-field rec-unito 'eta))
  (princ "\n\nRecord dopo rimozione campo 'eta':")
  (stampa-record rec-senza-eta)
  (setq ha-nome (has-field rec-unito 'nome))
  (setq ha-telefono (has-field rec-unito 'telefono))
  (princ (strcat "\n\nHa campo 'nome'? " (if ha-nome "SI" "NO")))
  (princ (strcat "\nHa campo 'telefono'? " (if ha-telefono "SI" "NO")))
  (princ "\n\n=== Demo completata ===")
  (princ))
;;; DEMO-FILTRO
;;; Dimostra filtraggio con funzione custom
(defun c:demo-record-filtro ()
  (princ "\n=== DEMO FILTRO RECORD ===")
  (setq prodotti '(((nome . "Prodotto A") (prezzo . 150) (categoria . "Elettronica"))
                   ((nome . "Prodotto B") (prezzo . 80) (categoria . "Casa"))
                   ((nome . "Prodotto C") (prezzo . 200) (categoria . "Elettronica"))
                   ((nome . "Prodotto D") (prezzo . 45) (categoria . "Casa"))
                   ((nome . "Prodotto E") (prezzo . 120) (categoria . "Sport"))))
  (princ "\n\nCatalogo completo:")
  (stampa-lista-record prodotti)
  (setq costosi (filter-records
                  '(lambda (r) (> (cdr (assoc 'prezzo r)) 100))
                  prodotti))
  (princ "\n\n\nProdotti con prezzo > 100:")
  (stampa-lista-record costosi)
  (setq elettronica (query-records 'categoria "Elettronica" prodotti))
  (princ "\n\n\nProdotti categoria Elettronica:")
  (if (= elettronica 'ERRORE)
    (princ "\nNessun prodotto trovato!")
    (stampa-lista-record elettronica))
  (princ "\n\n=== Demo completata ===")
  (princ))
;;; DEMO-TUTTO-RECORD
;;; Esegue tutte le demo sui record
(defun c:demo-record-tutto ()
  (princ "\n")
  (princ "\n+========================================================+")
  (princ "\n|  UTILITA' RECORD - DIMOSTRAZIONE COMPLETA             |")
  (princ "\n+========================================================+")
  (princ "\n")
  (c:demo-record-base)
  (princ "\n\nPremi Invio per continuare...") (getstring)
  (c:demo-record-db)
  (princ "\n\nPremi Invio per continuare...") (getstring)
  (c:demo-record-avanzate)
  (princ "\n\nPremi Invio per continuare...") (getstring)
  (c:demo-record-filtro)
  (princ "\n")
  (princ "\n+========================================================+")
  (princ "\n|         TUTTE LE DEMO RECORD COMPLETATE                |")
  (princ "\n+========================================================+")
  (princ))
