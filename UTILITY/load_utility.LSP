(setq #pathLisp "c:/lisp2025/utility/")
(load (strcat #pathLisp "_princ.lsp"))
(load (strcat #pathLisp "_stringhe.lsp"))
(load (strcat #pathLisp "_punti.lsp"))
(load (strcat #pathLisp "_liste.lsp"))
(load (strcat #pathLisp "_record.lsp"))
(load (strcat #pathLisp "_entita.lsp"))
(load (strcat #pathLisp "_gruppi.lsp"))
(load (strcat #pathLisp "_layer.lsp"))
(load (strcat #pathLisp "_mat.lsp"))
(load (strcat #pathLisp "_linee.lsp"))
(load (strcat #pathLisp "_polilinee.lsp"))
(load (strcat #pathLisp "_dcl.lsp"))
(load (strcat #pathLisp "_file.lsp"))
(load (strcat #pathLisp "_xdata.lsp"))
